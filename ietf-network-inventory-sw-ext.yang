module ietf-network-inventory-sw-ext {
  yang-version 1.1;
  namespace
    "urn:ietf:params:xml:ns:yang:ietf-network-inventory-sw-ext";
  prefix nwis;

  import ietf-yang-types {
    prefix yang;
    reference
      "RFC 9911: Common YANG Data Types";
  }
  import ietf-network-inventory {
    prefix nwi;
    reference
      "RFCAAAA: A YANG Data Model for Network Inventory";
  }

  organization
    "IETF Network Inventory YANG (ivy) Working Group";
  contact
    "WG Web:   <https://datatracker.ietf.org/wg/ivy>
     WG List:  <mailto:inventory-yang@ietf.org>

     Editor: Bo Wu
             <lana.wubo@huawei.com>
     Editor: Cheng Zhou
          <zhouchengyjy@chinamobile.com>
     Editor: Qin Wu
             <bill.wu@huawei.com>
     Editor: Mohamed Boucadair
             <mohamed.boucadair@orange.com>";
  description
    "This YANG module defines a model for network inventory software
     extensions.

     Copyright (c) 2026 IETF Trust and the persons
     identified as authors of the code.  All rights reserved.

     Redistribution and use in source and binary forms, with or
     without modification, is permitted pursuant to, and subject
     to the license terms contained in, the Revised BSD License
     set forth in Section 4.c of the IETF Trust's Legal Provisions
     Relating to IETF Documents
     (https://trustee.ietf.org/license-info).

     This version of this YANG module is part of RFC XXXX; see
     the RFC itself for full legal notices.";

  revision 2026-04-15 {
    description
      "Initial version";
    reference
      "RFC XXXX: A YANG Data Model for Network Inventory Software
                 Extensions.";
  }

  identity ne-nonphysical {
    base nwi:ne-type;
    description
      "Any network element implemented purely in software.
       It performs protocol or forwarding functions but
       does not correspond to a distinguishable hardware
       chassis. It can be hosted on a bare-metal server,
       VM, container, or cloud instance.";
  }

  identity ne-software {
    base ne-nonphysical;
    description
      "Software NE that runs directly on a host OS
       (also known as bare-metal deployment) or hypervisor.
       Examples of software NEs are network controllers.";
  }

  identity ne-virtual {
    base ne-nonphysical;
    description
      "Virtual NE instantiated inside a virtual-machine
       (VM). Provides virtual network function (VNF) implementations
       such as vRouter, vFirewall, vPE.";
  }

  identity ne-container {
    base ne-nonphysical;
    description
      "Container NE packaged as CNF (Containerised Network
       Function). Runs under Docker/K8s.";
  }

  identity software-component {
    base nwi:non-hardware-component-class;
    description
      "Base identity for software components in a managed device.";
  }

  identity operating-system {
    base software-component;
    description
      "Operating system software type.";
  }

  identity bios {
    base software-component;
    description
      "System firmware responsible for hardware initialization
     and system boot.";
  }

  identity boot-loader {
    base software-component;
    description
      "Software layer responsible for loading and booting the
       device OS or network OS.";
  }

  identity software-module {
    base software-component;
    description
      "Installable unit smaller than a full OS image,
       e.g., feature package.";
  }

  identity software-status {
    description
      "Base identity for software status.";
  }

  identity software-installed {
    base software-status;
    description
      "Software or patch is installed on the network element
          or component but not yet active.";
  }

  identity software-activated {
    base software-status;
    description
      "Software or patch is active and taking effect
          on the network element or component.";
  }

  grouping software-info-grouping {
    description
      "Specific attributes applicable to software.";
    leaf status {
      type identityref {
        base software-status;
      }
      description
        "Software status.";
    }
    leaf installation-time {
      type yang:date-and-time;
      description
        "Time when the software or patch revision was
         first installed.";
    }
    leaf activation-time {
      type yang:date-and-time;
      description
        "Time when the currently installed revision became active
         (i.e., was rebooted into).";
    }
  }

  /* Main blocks */

  augment "/nwi:network-inventory/nwi:network-elements"
        + "/nwi:network-element/nwi:software-rev" {
    description
      "Adds installation-/activation-time, status, etc. to the base
       NE software revision.";
    uses software-info-grouping;
  }

  augment "/nwi:network-inventory/nwi:network-elements"
        + "/nwi:network-element/nwi:software-rev/nwi:patch" {
    description
      "Adds installation-/activation-time, status, etc. to the patch
       level.";
    uses software-info-grouping;
  }

  augment "/nwi:network-inventory/nwi:network-elements/"
        + "nwi:network-element/nwi:components/nwi:component/"
        + "nwi:software-rev" {
    description
      "Extends components, such as line-card/CPU/etc.
       software revision with timestamp and state information.";
    uses software-info-grouping;
  }

  augment "/nwi:network-inventory/nwi:network-elements/"
        + "nwi:network-element/nwi:components/nwi:component/"
        + "nwi:software-rev/nwi:patch" {
    description
      "Applies the software-info attributes to component-level
       patches.";
    uses software-info-grouping;
  }
}
